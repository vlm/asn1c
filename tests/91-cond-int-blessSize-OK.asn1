-- OK: Everything is fine

-- iso.org.dod.internet.private.enterprise (1.3.6.1.4.1)
-- .spelio.software.asn1c.test (9363.1.5.1)
-- .91

ModuleConditionalIntegerType-with-fblessSIZE
	{ iso org(3) dod(6) internet (1) private(4) enterprise(1)
		spelio(9363) software(1) asn1c(5) test(1) 91 }
DEFINITIONS ::=
BEGIN

	OK-Integer1 ::= INTEGER (SIZE(1))
	OK-Integer2 ::= INTEGER (SIZE(2))
	OK-Integer3 ::= INTEGER (SIZE(3))
	OK-Integer4 ::= INTEGER (SIZE(4))
	NO-Integer5 ::= INTEGER (SIZE(5))

END
