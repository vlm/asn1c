-- OK: Everything is Fine

-- iso.org.dod.internet.private.enterprise (1.3.6.1.4.1)
-- .spelio.software.asn1c.test (9363.1.5.1)
-- .72

ModuleTestSameNames
	{ iso org(3) dod(6) internet(1) private(4) enterprise(1)
		spelio(9363) software(1) asn1c(5) test(1) 72 }
	DEFINITIONS ::=
BEGIN

	/*
	 * This test checks whether different top-level types containing
	 * similarly named inner types may be compiled by the target language
	 * compiler successfully. This was not the case before asn1c-0.9.11.
	 */

	Type ::= SET OF SEQUENCE {
			t1	Type1,
			t2	Type2
		}

	Type1 ::= SEQUENCE {
		one-name CHOICE {
			another-name SEQUENCE { a INTEGER, b INTEGER }
		}
	}

	Type2 ::= CHOICE {
		one-name SEQUENCE {
			another-name SEQUENCE {
				a BIT STRING { one(0) } SIZE(2),
				b INTEGER
			}
		},
		two-name SET {
			another-name SEQUENCE {
				a BIT STRING { one(0) } SIZE(2),
				b INTEGER
			}
		}
	}

END
