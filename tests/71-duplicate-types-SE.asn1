-- OK: Everything is fine

-- iso.org.dod.internet.private.enterprise (1.3.6.1.4.1)
-- .spelio.software.asn1c.test (9363.1.5.1)
-- .71

ModuleDuplicateTypes1
	{ iso org(3) dod(6) internet(1) private(4) enterprise(1)
		spelio(9363) software(1) asn1c(5) test(1) 71 1 }
	DEFINITIONS ::=
BEGIN

	Type ::= INTEGER	-- Original type.

END

ModuleDuplicateTypes2
	{ iso org(3) dod(6) internet(1) private(4) enterprise(1)
		spelio(9363) software(1) asn1c(5) test(1) 71 2 }
	DEFINITIONS ::=
BEGIN

	Type ::= INTEGER	-- A duplicate type.

END
