-- OK: Everything is Fine

-- iso.org.dod.internet.private.enterprise (1.3.6.1.4.1)
-- .spelio.software.asn1c.test (9363.1.5.1)
-- .37

ModuleTestIndirectChoiceFine
	{ iso org(3) dod(6) internet(1) private(4) enterprise(1)
		spelio(9363) software(1) asn1c(5) test(1) 37 }
	DEFINITIONS IMPLICIT TAGS ::=
BEGIN

	T ::= CHOICE {
		t-a  INTEGER,
		t-b  OCTET STRING,
		t-c  [1] Choice1,
		t-d  [3] Choice2
	}

	Choice1 ::= CHOICE {
		c-a OCTET STRING,
		c-b INTEGER
	}

	Choice2 ::= [2] CHOICE {
		c-a OCTET STRING,
		c-b INTEGER,
		c-d [3] Choice1,
		c-e [4] Choice1
	}

	Choice3 ::= [3] EXPLICIT Choice2		-- tags [3] [2]
	Choice4 ::= [4] IMPLICIT Choice2		-- tags [4]
	Choice5 ::= Choice2				-- tags [2]
	Choice6 ::= Choice1				-- tags

END
