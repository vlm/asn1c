-- OK: Everything is fine

-- iso.org.dod.internet.private.enterprise (1.3.6.1.4.1)
-- .spelio.software.asn1c.test (9363.1.5.1)
-- .74

ModuleTestIntegerAndEnumeratedConstraints
	{ iso org(3) dod(6) internet (1) private(4) enterprise(1)
		spelio(9363) software(1) asn1c(5) test(1) 74 }
	DEFINITIONS ::=
BEGIN

	-- Enumeration constrained by the second choice.
	Enum ::= ENUMERATED { one, two } (two|one)

	-- Integer constrained by the only choice.
	Int ::= INTEGER { v1-0(123) } (v1-0)

	EnumRef ::= Enum (two)

END
