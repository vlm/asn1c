-- OK: Everything is fine

-- iso.org.dod.internet.private.enterprise (1.3.6.1.4.1)
-- .spelio.software.asn1c.test (9363.1.5.1)
-- .17

ModuleTestTags
	{ iso org(3) dod(6) internet(1) private(4) enterprise(1)
		spelio(9363) software(1) asn1c(5) test(1) 17 }
	DEFINITIONS ::=
BEGIN

	T3 ::= [3] IMPLICIT T2
	T1 ::= [1] INTEGER
	T2 ::= [2] EXPLICIT T1

	T4 ::= [APPLICATION 1] SET {
			t1	[4] IMPLICIT T1,
			t2	[5] T2,
			t3	[6] T3
		}

END
