-- SE: Semantic error

-- iso.org.dod.internet.private.enterprise (1.3.6.1.4.1)
-- .spelio.software.asn1c.test (9363.1.5.1)
-- .15 1
-- .15 2

ModuleTestResolver4
	{ iso org(3) dod(6) internet(1) private(4) enterprise(1)
		spelio(9363) software(1) asn1c(5) test(1) 15 1 }
	DEFINITIONS ::=
BEGIN
	IMPORTS Enumeration, beta FROM
		OtherModuleRenamed
		{ iso org(3) dod(6) internet(1) private(4) enterprise(1)
			spelio(9363) software(1) asn1c(5) test(1) 15 2 };

	-- external reference
	alpha Enumeration ::= beta

END

ModuleTestResolver5
	{ iso org(3) dod(6) internet(1) private(4) enterprise(1)
		spelio(9363) software(1) asn1c(5) test(1) 15 2 }
	DEFINITIONS ::=
BEGIN
	EXPORTS;	-- Does not export anything!

	beta Enumeration ::= b

	Enumeration ::= ENUMERATED { a(1), b(2) }

END
