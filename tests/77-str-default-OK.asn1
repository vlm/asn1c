-- OK: Everything is fine

-- iso.org.dod.internet.private.enterprise (1.3.6.1.4.1)
-- .spelio.software.asn1c.test (9363.1.5.1)
-- .77

ModuleTestStringDefault1
	{ iso org(3) dod(6) internet(1) private(4) enterprise(1)
		spelio(9363) software(1) asn1c(5) test(1) 77 }
	DEFINITIONS AUTOMATIC TAGS ::=
BEGIN

	Type ::= SEQUENCE {
		cntry  PRString DEFAULT country1,
		cntry1 PrintableString DEFAULT country1,
		cntry2 UniversalString DEFAULT country2,
		...
	}

	country1 PrintableString ::= "Rwanda"
	country2 PRString ::= "United Kingdom"

	PRString ::= PrintableString

END
