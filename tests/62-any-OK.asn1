-- OK: Everything is fine

-- iso.org.dod.internet.private.enterprise (1.3.6.1.4.1)
-- .spelio.software.asn1c.test (9363.1.5.1)
-- .62

ModuleTestANYSyntax
	{ iso org(3) dod(6) internet(1) private(4) enterprise(1)
		spelio(9363) software(1) asn1c(5) test(1) 62 }
	DEFINITIONS IMPLICIT TAGS ::=
BEGIN

	T ::= CHOICE {
		s1 T1-ext,
		s2 T2,
		s3 T3
	}

	T1-ext ::= SEQUENCE {
		i	INTEGER OPTIONAL,
		any	[1] ANY,	-- Converted into [1] EXPLICIT ANY
		...
	}

	T2 ::= [16] SEQUENCE {
		m1  [0] NumericString,
		m2  [1] BOOLEAN,
		m3  [3] SEQUENCE OF NumericString,
		o4  [4] BOOLEAN OPTIONAL,
		o5  [5] BOOLEAN OPTIONAL,
		o6  [6] BOOLEAN OPTIONAL
	}

	T3 ::= SET {
		m1  [0] NumericString,
		m2  [1] BOOLEAN
	}

END
