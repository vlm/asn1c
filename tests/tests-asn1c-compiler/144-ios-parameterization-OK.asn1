-- OK: Everything is fine

-- iso.org.dod.internet.private.enterprise (1.3.6.1.4.1)
-- .spelio.software.asn1c.test (9363.1.5.1)
-- .144

ModuleInformationObjectParameterization
	{ iso org(3) dod(6) internet (1) private(4) enterprise(1)
		spelio(9363) software(1) asn1c(5) test(1) 144 }
	DEFINITIONS ::=
BEGIN

    MYID ::= CLASS {
        &id     INTEGER UNIQUE,
        &Type
    } WITH SYNTAX {&Type IDENTIFIED BY &id}

    RegionalExtension MYID ::= {
        {INTEGER IDENTIFIED BY 1} |
        {BOOLEAN IDENTIFIED BY 2},
        ...
    }

    Message ::= SEQUENCE {
        content SpecializedContent {{RegionalExtension}}
    }

    SpecializedContent {MYID : Set} ::= SEQUENCE {
        id      MYID.&id({Set}),
        value   MYID.&Type({Set}{@id})
    }

END
