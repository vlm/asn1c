-- OK: Everything is fine

-- iso.org.dod.internet.private.enterprise (1.3.6.1.4.1)
-- .spelio.software.asn1c.test (9363.1.5.1)
-- .24

ModuleTestSequence
	{ iso org(3) dod(6) internet(1) private(4) enterprise(1)
		spelio(9363) software(1) asn1c(5) test(1) 24 }
	DEFINITIONS IMPLICIT TAGS ::=
BEGIN

	T ::= [5] EXPLICIT SEQUENCE {
		a		INTEGER,
		b [0]		INTEGER OPTIONAL,
		c [1]		INTEGER DEFAULT ten,
		d [5] EXPLICIT	INTEGER
		}

	ten INTEGER ::= 10

END
