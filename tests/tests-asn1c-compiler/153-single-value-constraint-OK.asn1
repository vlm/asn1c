-- OK: Everything is fine

-- iso.org.dod.internet.private.enterprise (1.3.6.1.4.1)
-- .spelio.software.asn1c.test (9363.1.5.1)
-- .153

ModuleSingleValueConstraint
	{ iso org(3) dod(6) internet(1) private(4) enterprise(1)
		spelio(9363) software(1) asn1c(5) test(1) 153 }
DEFINITIONS ::= BEGIN

    zero8 OCTET STRING ::= '0000000000000000'H

    Index ::= SEQUENCE {
        padding OCTET STRING (SIZE(8)) (zero8)
    }

END
