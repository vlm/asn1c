-- OK: Everything is fine

-- iso.org.dod.internet.private.enterprise (1.3.6.1.4.1)
-- .spelio.software.asn1c.test (9363.1.5.1)
-- .158

ModuleTestSequenceOfSequenceNested
	{ iso org(3) dod(6) internet(1) private(4) enterprise(1)
		spelio(9363) software(1) asn1c(5) test(1) 158 }
	DEFINITIONS IMPLICIT TAGS ::=
BEGIN

	SeqWithNestedSOS ::= SEQUENCE {
		someString [0] UTF8String,
		sos [1] SEQUENCE OF SEQUENCE {
			anotherString [2] UTF8String,
			nested-sos [3] SEQUENCE OF SEQUENCE {
				nested-string [4] UTF8String
			}
		}
	}

END
