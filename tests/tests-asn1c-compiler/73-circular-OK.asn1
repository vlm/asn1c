-- OK: Everything is Fine

-- iso.org.dod.internet.private.enterprise (1.3.6.1.4.1)
-- .spelio.software.asn1c.test (9363.1.5.1)
-- .73

ModuleTestCircularReferences
	{ iso org(3) dod(6) internet(1) private(4) enterprise(1)
		spelio(9363) software(1) asn1c(5) test(1) 73 }
	DEFINITIONS ::=
BEGIN

	Type ::= SEQUENCE {
		data SEQUENCE OF EpytRef
	}

	EpytRef ::= Epyt

	Epyt ::= SEQUENCE {
		stype	SET OF Type,
		type	Type OPTIONAL,
		ypet	Ypet OPTIONAL
	}

	Ypet ::= SET {
		epyt	Epyt,
		plain	INTEGER DEFAULT 7,
		senums	SET OF EnumType,
		patest1	[1] IA5String (FROM("A".."Z")),
		patest2	[2] IA5String (FROM("a".."z"))
	}

	EnumType ::= ENUMERATED { one, two }

END
