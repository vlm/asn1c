-- OK: Everything is fine

-- iso.org.dod.internet.private.enterprise (1.3.6.1.4.1)
-- .spelio.software.asn1c.test (9363.1.5.1)
-- .165

-- Forward compatibility of UPER decoding: this module is the OLD
-- version of the protocol.  The test decodes byte streams produced
-- by a NEWER version (with extension additions after "...") and
-- expects the unknown extensions to be skipped, with all root fields
-- recovered.

ModuleUPERExtensionSkip
	{ iso org(3) dod(6) internet (1) private(4) enterprise(1)
		spelio(9363) software(1) asn1c(5) test(1) 165 }
	DEFINITIONS AUTOMATIC TAGS ::=
BEGIN

	T ::= SEQUENCE {
		seq1 MsgCount,
		...
	}

	C ::= CHOICE {
		c1 MsgCount,
		c2 MsgCount,
		...
	}

	N ::= SEQUENCE {
		a MsgCount,
		ch C,
		b MsgCount
	}

	M ::= SEQUENCE {
		a MsgCount,
		t T,
		b MsgCount
	}

	MsgCount ::= INTEGER (0..127)

END
