-- OK: Everything is fine

-- iso.org.dod.internet.private.enterprise (1.3.6.1.4.1)
-- .spelio.software.asn1c.test (9363.1.5.1)
-- .159

ModuleA
	{ iso org(3) dod(6) internet(1) private(4) enterprise(1)
		spelio(9363) software(1) asn1c(5) test(1) 159 }
DEFINITIONS IMPLICIT TAGS ::=
BEGIN

Rate ::= INTEGER(0..65535)
c-Rate INTEGER ::= 2
EXT-TYPE ::= CLASS {
      &extRef RefExt UNIQUE,
      &ExtValue
    }
    WITH SYNTAX {&ExtValue IDENTIFIED BY &extRef}
RefExt::=INTEGER (0..255)

END

ModuleB
DEFINITIONS IMPLICIT TAGS ::=
BEGIN

Rate ::= INTEGER(0..255)
c-Rate INTEGER ::= 1

END

ModuleC
DEFINITIONS IMPLICIT TAGS ::=
BEGIN
IMPORTS
	Rate, EXT-TYPE FROM ModuleA
	c-Repeat FROM ModuleB;

ExtTypes EXT-TYPE ::= {
	{ Rate IDENTIFIED BY c-Rate },
	...
	}

END
