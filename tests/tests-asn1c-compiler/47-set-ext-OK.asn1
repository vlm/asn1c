-- OK: Everything is fine

-- iso.org.dod.internet.private.enterprise (1.3.6.1.4.1)
-- .spelio.software.asn1c.test (9363.1.5.1)
-- .47

ModuleSetChoiceExtensibility
	{ iso org(3) dod(6) internet (1) private(4) enterprise(1)
		spelio(9363) software(1) asn1c(5) test(1) 47 }
	DEFINITIONS IMPLICIT TAGS EXTENSIBILITY IMPLIED ::=
BEGIN

	T1 ::= SET { i INTEGER }
	T2 ::= SET { i INTEGER, ... }
	T3 ::= CHOICE { i INTEGER }
	T4 ::= CHOICE { i INTEGER, ... }

END
