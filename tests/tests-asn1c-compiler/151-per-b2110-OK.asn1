-- OK: Everything is fine

-- iso.org.dod.internet.private.enterprise (1.3.6.1.4.1)
-- .spelio.software.asn1c.test (9363.1.5.1)
-- .151

ModulePerEffectiveConstraint
	{ iso org(3) dod(6) internet(1) private(4) enterprise(1)
		spelio(9363) software(1) asn1c(5) test(1) 151 }
DEFINITIONS ::= BEGIN

    -- B.2.1.10
    -- Effective constraint: SIZE(3..20) and FROM("A".."K")
    B ::= VisibleString (SIZE (20) INTERSECTION FROM ("A".."F")
                    UNION SIZE (3) INTERSECTION FROM ("F".."K"))

END
