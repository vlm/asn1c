-- OK: Everything is fine

-- iso.org.dod.internet.private.enterprise (1.3.6.1.4.1)
-- .spelio.software.asn1c.test (9363.1.5.1)
-- .142
ModuleTestAnonTypeDecoration
	{ iso org(3) dod(6) internet(1) private(4) enterprise(1)
		spelio(9363) software(1) asn1c(5) test(1) 142 }

DEFINITIONS AUTOMATIC TAGS ::= BEGIN 
 
CommonType ::= CHOICE  {
    t1 Type1,
    t2 Type2
}

Type1 ::= CHOICE  {
    anonType SEQUENCE  {
        x OCTET STRING (SIZE (32)),
        y OCTET STRING (SIZE (32))
    }
}

Type2 ::= CHOICE  {
    anonType SEQUENCE  {
        x OCTET STRING (SIZE (48)),
        y OCTET STRING (SIZE (48))
    }
}

END
