-- OK: Everything is fine

-- iso.org.dod.internet.private.enterprise (1.3.6.1.4.1)
-- .spelio.software.asn1c.test (9363.1.5.1)
-- .135

ModuleOERShort
	{ iso org(3) dod(6) internet (1) private(4) enterprise(1)
		spelio(9363) software(1) asn1c(5) test(1) 135 }
	DEFINITIONS IMPLICIT TAGS ::=
BEGIN

    -- Supported only on 64-bit platforms.
    T ::= SEQUENCE {
        unsigned8         [0] INTEGER (0..255),       -- OER 1 byte
        unsigned16       [1]  INTEGER (0..65535),     -- OER 2 bytes
        unsigned16stack [2] INTEGER (0..32767)(0..255), --  OER 1 byte
        unsigned16stack-ext [15] INTEGER (0..32767)(0..255,...), -- OER 2 bytes
        ...,
        signed8           [10] INTEGER (-128..127) DEFAULT 3, -- OER 1 byte
        signed16          [11] INTEGER (-32768..32767),    -- OER 2 bytes
        signed16stack     [12] INTEGER (-32768..32767)(-128..127), -- OER 1 byte
        signed16stack-ext [5] INTEGER (-32768..32767)(-128..127,...), -- OER 2 b
        signed32          [7] INTEGER (-2000000000..2000000000), -- OER 4 bytes
        ...,
        minmax            [6] INTEGER (MIN..MAX) OPTIONAL
    }

END
