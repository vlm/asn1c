-- OK: Everything is fine

-- iso.org.dod.internet.private.enterprise (1.3.6.1.4.1)
-- .spelio.software.asn1c.test (9363.1.5.1)
-- .106

ModuleParameterizationWithConstraints
	{ iso org(3) dod(6) internet (1) private(4) enterprise(1)
		spelio(9363) software(1) asn1c(5) test(1) 106 }
	DEFINITIONS ::=
BEGIN

	Narrow {Type, INTEGER:value} ::= SEQUENCE {
		narrow1	Type (1..5)	DEFAULT value,
		narrow2	[0] Type (2..5),
		narrow3	[1] Type (3..5)	OPTIONAL
	}

	NarrowInteger ::= Narrow {INTEGER (0..10), 3}

END
