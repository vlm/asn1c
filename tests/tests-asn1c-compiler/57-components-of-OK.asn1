-- OK: Everything is fine

-- iso.org.dod.internet.private.enterprise (1.3.6.1.4.1)
-- .spelio.software.asn1c.test (9363.1.5.1)
-- .57

ModuleTestComponentsOfCrossModule1
	{ iso org(3) dod(6) internet(1) private(4) enterprise(1)
		spelio(9363) software(1) asn1c(5) test(1) 57 1 }
	DEFINITIONS AUTOMATIC TAGS ::=
BEGIN

	SecondType ::= SEQUENCE {
		a	IA5String,
		COMPONENTS OF ModuleTestComponentsOfCrossModule2.OneType,
		b	UniversalString
	}

END

ModuleTestComponentsOfCrossModule2
	{ iso org(3) dod(6) internet(1) private(4) enterprise(1)
		spelio(9363) software(1) asn1c(5) test(1) 57 2 }
	DEFINITIONS EXPLICIT TAGS ::=
BEGIN

	OneType ::= SEQUENCE {
		x	T1,
		y	T2,
		z	T3
	}

	T1 ::= INTEGER
	T2 ::= INTEGER
	T3 ::= INTEGER

END
