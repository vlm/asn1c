-- OK: Everything is fine

-- Regression test for CVE-2025-32893: an Information Object Set used to
-- parameterize a type was deduplicated against another Information Object
-- Set that differed ONLY by its VALUESET reference. Because
-- asn1p_expr_compare() did not compare the `constraints` field,
-- asn1f_parameterization_fork() failed to fork the two parameterizations,
-- and the second usage silently reused the first value set's information
-- object table (lack of input validation). With the fix the two usages
-- generate distinct, complete tables (SetA -> _46P0, SetB -> _46P1).

-- iso.org.dod.internet.private.enterprise (1.3.6.1.4.1)
-- .spelio.software.asn1c.test (9363.1.5.1)
-- .163

ModuleIosValuesetFork
	{ iso org(3) dod(6) internet (1) private(4) enterprise(1)
		spelio(9363) software(1) asn1c(5) test(1) 163 }
	DEFINITIONS ::=
BEGIN

    MYID ::= CLASS {
        &id     INTEGER UNIQUE,
        &Type
    } WITH SYNTAX {&Type IDENTIFIED BY &id}

    SetA MYID ::= {
        {INTEGER IDENTIFIED BY 1} |
        {BOOLEAN IDENTIFIED BY 2},
        ...
    }

    SetB MYID ::= {
        {OCTET STRING IDENTIFIED BY 3} |
        {IA5String IDENTIFIED BY 4},
        ...
    }

    Message ::= SEQUENCE {
        first   SpecializedContent {{SetA}},
        second  SpecializedContent {{SetB}}
    }

    SpecializedContent {MYID : Set} ::= SEQUENCE {
        id      MYID.&id({Set}),
        value   MYID.&Type({Set}{@id})
    }

END
