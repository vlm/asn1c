-- OK: Everything is fine

-- iso.org.dod.internet.private.enterprise (1.3.6.1.4.1)
-- .spelio.software.asn1c.test (9363.1.5.1)
-- .167

-- A SIZE constraint with extension additions, e.g. SIZE(2,...,3):
-- the PER-visible root is SIZE(2), and the named extension size (3)
-- must be encoded as an extension (general length determinant),
-- not folded into the root range.

ModulePERSizeExtension
	{ iso org(3) dod(6) internet (1) private(4) enterprise(1)
		spelio(9363) software(1) asn1c(5) test(1) 167 }
	DEFINITIONS AUTOMATIC TAGS ::=
BEGIN

	T ::= BIT STRING (SIZE(2,...,3))

	O ::= OCTET STRING (SIZE(2,...,3))

END
