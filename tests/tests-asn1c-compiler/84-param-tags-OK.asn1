-- OK: Everything is fine

-- iso.org.dod.internet.private.enterprise (1.3.6.1.4.1)
-- .spelio.software.asn1c.test (9363.1.5.1)
-- .84 1
-- .84 2

ModuleTestParameterizationTags1
	{ iso org(3) dod(6) internet(1) private(4) enterprise(1)
		spelio(9363) software(1) asn1c(5) test(1) 84 1 }
	DEFINITIONS ::=
BEGIN

	TestType {Parameter} ::= SEQUENCE { 
		common	Parameter	DEFAULT 0
	} 

	TestChoice ::= CHOICE { 
		type1 TestType {INTEGER (1..10)},
		type2 [0] IMPLICIT TestType {BOOLEAN} 
	} 

END

ModuleTestParameterizationTagsAuto2
	{ iso org(3) dod(6) internet(1) private(4) enterprise(1)
		spelio(9363) software(1) asn1c(5) test(1) 84 2 }
	DEFINITIONS AUTOMATIC TAGS ::=
BEGIN

	AutoType {Parameter} ::= SEQUENCE { 
		common Parameter (0)
	} 

	AutoChoice ::= CHOICE { 
		type1 AutoType {INTEGER (0..1)},
		type2 AutoType {BOOLEAN}
	} 

END
