-- OK: Everything is fine

-- iso.org.dod.internet.private.enterprise (1.3.6.1.4.1)
-- .spelio.software.asn1c.test (9363.1.5.1)
-- .3

ModuleTestEnum1
	{ iso org(3) dod(6) internet (1) private(4) enterprise(1)
		spelio(9363) software(1) asn1c(5) test(1) 3 }
	DEFINITIONS ::=
BEGIN

	Enum1 ::= ENUMERATED
		{ red,	-- will be 0 --
		green,	-- will be 1 --
		blue(4),
		alpha,
		... -- extensible --
		}

	Enum2 ::= ENUMERATED
		{ red,	-- will be 0 --
		green,	-- will be 1 --
		blue(45),
		orange(23),	-- Does not have to be ordered --
		alpha,
		..., -- extensible --
		beta(12),	-- May be less than the max value in the root --
		gamma(103)	-- Must be ordered --
		}

	Enum3 ::= ENUMERATED { a, b(3), ..., c(1) }
	Enum4 ::= ENUMERATED { a, b, ..., c(3), d }
	Enum5 ::= ENUMERATED { a, z(25), ..., d }

END
