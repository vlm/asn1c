-- OK: Everything is fine

-- iso.org.dod.internet.private.enterprise (1.3.6.1.4.1)
-- .spelio.software.asn1c.test (9363.1.5.1)
-- .19

ModuleTestParam
	{ iso org(3) dod(6) internet(1) private(4) enterprise(1)
		spelio(9363) software(1) asn1c(5) test(1) 19 }
	DEFINITIONS ::=
BEGIN

	SIGNED { ToBeSigned } ::= SEQUENCE {
		toBeSigned	ToBeSigned,
		algorithm	OBJECT IDENTIFIER,
		signature	BIT STRING (SIZE(0..256))
	}

	Certificate ::= SIGNED { SEQUENCE {
		version		INTEGER,
		signature	OBJECT IDENTIFIER,
		issuer		Name
	} }

	Name ::= SEQUENCE OF RelativeDistinguishedName

	RelativeDistinguishedName ::= SET SIZE (1..MAX) OF
		IA5String (FROM("A".."Z"|"a".."z"|"0-9"|",-."))

END
