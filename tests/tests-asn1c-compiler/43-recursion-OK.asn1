-- OK: Everything is fine

-- iso.org.dod.internet.private.enterprise (1.3.6.1.4.1)
-- .spelio.software.asn1c.test (9363.1.5.1)
-- .43

ModuleRecursion
	{ iso org(3) dod(6) internet (1) private(4) enterprise(1)
		spelio(9363) software(1) asn1c(5) test(1) 43 }
	DEFINITIONS ::=
BEGIN

	Test-structure-1 ::= SEQUENCE {
		t-member1 SET OF Test-structure-1,
		t-member2 SEQUENCE OF Test-structure-1,
		t-member3 Test-structure-1 OPTIONAL,
		t-member4 INTEGER
	}

	Choice-1 ::= CHOICE {
		and   [1] Choice-1,
		or    [2] IMPLICIT SET OF Choice-1,
		not   [3] Choice-1,
		other [4] INTEGER
	}

	Test-structure-2 ::= SET { m1 Test-structure-3 OPTIONAL }
	Test-structure-3 ::= SET { m1 Test-structure-2 OPTIONAL }

END
