-- OK: Everything is fine

-- iso.org.dod.internet.private.enterprise (1.3.6.1.4.1)
-- .spelio.software.asn1c.test (9363.1.5.1)
-- .150

ModuleValueWithComponents
	{ iso org(3) dod(6) internet(1) private(4) enterprise(1)
		spelio(9363) software(1) asn1c(5) test(1) 150 }
DEFINITIONS ::= BEGIN

    EntityType ::= BIT STRING {app (0), enrol (1)} (SIZE (8))

    GroupPermissions ::= SEQUENCE {
        minChainDepth   INTEGER DEFAULT 1,
        eeType          EntityType DEFAULT {app}
    }

    EnrolPermissions ::= GroupPermissions (WITH COMPONENTS {
        minChainDepth (2),
        eeType ({enrol})
    })

END
