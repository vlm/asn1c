-- OK: Everything is fine

-- iso.org.dod.internet.private.enterprise (1.3.6.1.4.1)
-- .spelio.software.asn1c.test (9363.1.5.1)
-- .159

ModuleExtensionGroups
    { iso org(3) dod(6) internet(1) private(4) enterprise(1)
        spelio(9363) software(1) asn1c(5) test(1) 159 }
DEFINITIONS AUTOMATIC TAGS ::= BEGIN

    maxValue INTEGER ::= 1023
    maxValue-Plus1 INTEGER ::= 1024

    maxValue-v1 INTEGER ::= 2047

    maxValue-v2 INTEGER ::= 4095

    ID ::= INTEGER (0..maxValue)

    ID-V1 ::= INTEGER (maxValue-Plus1..maxValue-v1)

    ID-V2 ::= INTEGER (0..maxValue-v2)

    ID-V3 ::= INTEGER (0..8192)

    ID-V4 ::= INTEGER (0..16383)

    MessageWithExtensionGrp ::= SEQUENCE {
        id           ID,
        data         OCTET STRING,
	...,
	[[ id-v1     ID-V1 OPTIONAL,
           data-v1   OCTET STRING (SIZE (64)) OPTIONAL
	]],
	[[ id-v2     ID-V2 OPTIONAL,
           data-v2   OCTET STRING (SIZE (0..256)) OPTIONAL
	]],
	[[ id-v3     ID-V3,
           data-v3   INTEGER (0..2048) OPTIONAL
	]],
	[[ id-v4     ID-V4 OPTIONAL,
           data-v4   BIT STRING (SIZE (0..128)) OPTIONAL
	]]
    }

END
