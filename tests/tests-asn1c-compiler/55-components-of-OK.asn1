-- OK: Everything is fine

-- iso.org.dod.internet.private.enterprise (1.3.6.1.4.1)
-- .spelio.software.asn1c.test (9363.1.5.1)
-- .55

ModuleTestComponentsOf
	{ iso org(3) dod(6) internet(1) private(4) enterprise(1)
		spelio(9363) software(1) asn1c(5) test(1) 55 }
	DEFINITIONS AUTOMATIC TAGS ::=
BEGIN

	OneType ::= SEQUENCE {
		one-1	    INTEGER,
		one-2	[1] BOOLEAN,
		one-3   SEQUENCE {
			alpha	INTEGER,
			beta	INTEGER,
			...
		},
		...,
		ignored-in-SecondType	INTEGER,
		...,
		one-4	INTEGER
	}

	SecondType ::= SEQUENCE {
		a	IA5String,
		COMPONENTS OF OneType,
		b	UniversalString
	}

END
