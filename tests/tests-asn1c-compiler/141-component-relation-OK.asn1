-- OK: Everything is fine

-- iso.org.dod.internet.private.enterprise (1.3.6.1.4.1)
-- .spelio.software.asn1c.test (9363.1.5.1)
-- .141

ModuleComponentRelationConstraint
	{ iso org(3) dod(6) internet (1) private(4) enterprise(1)
		spelio(9363) software(1) asn1c(5) test(1) 141 }
	DEFINITIONS AUTOMATIC TAGS ::=
BEGIN

    Frame ::= SEQUENCE {
        ident   FRAME-STRUCTURE.&id({FrameTypes}),
        value   FRAME-STRUCTURE.&Type({FrameTypes}{@.ident}),
        ...
    }

    FRAME-STRUCTURE ::= CLASS {
        &id    ConstrainedInteger UNIQUE,
        &Type
    } WITH SYNTAX {&Type IDENTIFIED BY &id}

    ConstrainedInteger ::= INTEGER (0..32767)

    FrameTypes FRAME-STRUCTURE ::= {
        { PrimitiveMessage IDENTIFIED BY primMessage } |
        { ComplexMessage IDENTIFIED BY cplxMessage }
        , ... }

    PrimitiveMessage ::= SEQUENCE {}
    ComplexMessage ::= SEQUENCE {}

    primMessage INTEGER ::= 1
    cplxMessage INTEGER ::= 2

END
