-- OK: Everything is Fine

-- iso.org.dod.internet.private.enterprise (1.3.6.1.4.1)
-- .spelio.software.asn1c.test (9363.1.5.1)
-- .38

ModuleNestedCTypeComments
	{ iso org(3) dod(6) internet(1) private(4) enterprise(1)
		spelio(9363) software(1) asn1c(5) test(1) 38 }
	DEFINITIONS ::=
BEGIN

	T ::= CHOICE {
		t-a  INTEGER,
		t-b  OCTET STRING
/*		t-c  [1] Choice1, t-d  Choice2 */
	}

	-- this is a comment too -- This-Is-Not-A-Comment
	::= INTEGER

/*
	ISO/IEC 8824-1 #11.6.4

	blah blah blah
	/* nested comment */
	-- this is an insignificant comment
	-- this is a comment too -- and this is a comment

 */

END
