-- OK: Everything is fine

-- iso.org.dod.internet.private.enterprise (1.3.6.1.4.1)
-- .spelio.software.asn1c.test (9363.1.5.1)
-- .176

-- Known-multiplier character strings with an extensible SIZE constraint.
-- When the length lies outside the extension root, X.691 #30.4 lifts the
-- size constraint only: the effective permitted-alphabet constraint (and
-- with it the per-character width, #30.5.2) still applies. The characters
-- must keep their alphabet-constrained width (7 bits for IA5String, 4 bits
-- for NumericString, 1 bit under FROM("AB"), 0 bits under FROM("A"))
-- instead of falling back to the canonical 8-bit units.
--
-- A/N/P/T/S carry named extension additions so that the tested
-- extension-region lengths are *legal* values of the type (X.680 §50.1):
-- every vector is validated with asn_check_constraints() before encoding.
-- T pins the X.691 #30.5.4 a) representability boundary: FROM(" ".."@")
-- has ub = 64 = 2^b, so direct character values do not fit and
-- canonical-order indexes are used. S pins the N = 1 alphabet: b = 0,
-- characters occupy no bits at all.
--
-- X uses a bare extension marker: per X.680 §50.1 NOTE 6 the value set is
-- the union of the root and the AdditionalElementSetSpec (when present),
-- so with no named additions the only legal length is the root; an
-- extension-region length is *not* a legal value, but per §52.1 it must
-- still decode without error; exercised as a forward-decode vector.
-- E permits the empty string in the root; EU only as a named extension
-- addition. Both guard the empty-input (units == 0) paths.

ModuleUPERStringSizeExtension
	{ iso org(3) dod(6) internet (1) private(4) enterprise(1)
		spelio(9363) software(1) asn1c(5) test(1) 176 }
	DEFINITIONS AUTOMATIC TAGS ::=
BEGIN

	A ::= IA5String (SIZE(1,...,4..9))

	N ::= NumericString (SIZE(2,...,3))

	P ::= IA5String (FROM("AB")) (SIZE(1,...,3))

	T ::= IA5String (FROM(" ".."@")) (SIZE(1,...,2))

	S ::= IA5String (FROM("A")) (SIZE(1,...,2))

	X ::= IA5String (SIZE(1,...))

	E ::= IA5String (SIZE(0,...,2))

	EU ::= IA5String (SIZE(1,...,0))

	W ::= SEQUENCE {
		v	A,
		trail	INTEGER (0..255)
	}

END
