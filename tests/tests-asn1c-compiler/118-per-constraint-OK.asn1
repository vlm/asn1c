-- OK: Everything is fine

-- iso.org.dod.internet.private.enterprise (1.3.6.1.4.1)
-- .spelio.software.asn1c.test (9363.1.5.1)
-- .118

ModuleConstraintPrecedence
	{ iso org(3) dod(6) internet (1) private(4) enterprise(1)
		spelio(9363) software(1) asn1c(5) test(1) 118 }
	DEFINITIONS ::=
BEGIN

	E1 ::= IA5String (SIZE(1..5, ...) ^ FROM("A".."Z")) 
	E2 ::= IA5String (SIZE(1..5,...,5)) (FROM("A".."Z")) 
	E3 ::= IA5String (SIZE(1..5) ^ FROM("A".."Z"),...)
	E4 ::= IA5String (FROM("A".."Z"),...) (SIZE(1..5)) 

	C ::= IA5String (SIZE(10) ^ FROM("A".."D")
			| SIZE(20) ^ FROM("D".."F"))

	P ::= IA5String (FROM("AB") ^ SIZE(1..2)
			 | FROM("DE") ^ SIZE(3)
			 | FROM("AXE") ^ SIZE(1..5))

END
