-- OK: Everything is fine

-- iso.org.dod.internet.private.enterprise (1.3.6.1.4.1)
-- .spelio.software.asn1c.test (9363.1.5.1)
-- .93

Module-asn1c-controls
	{ iso org(3) dod(6) internet (1) private(4) enterprise(1)
		spelio(9363) software(1) asn1c(5) test(1) 93 }
DEFINITIONS AUTOMATIC TAGS ::=
BEGIN

	Sequence ::= SEQUENCE {
		ainl INTEGER,
		--<ASN1C.RepresentAsPointer>--
		aptr INTEGER
	}

	Set ::= SET {
		ainl Sequence,
		--<ASN1C.RepresentAsPointer>--
		aptr Sequence
	}

	Choice ::= CHOICE {
		--<ASN1C.RepresentAsPointer>--
		setof SET OF INTEGER,
		--<ASN1C.RepresentAsPointer>--
		aptr Sequence,
		ainl Sequence
	}

END
