-- OK: Everything is Fine

-- iso.org.dod.internet.private.enterprise (1.3.6.1.4.1)
-- .spelio.software.asn1c.test (9363.1.5.1)
-- .67

ModuleTestEmbeddedChoice
	{ iso org(3) dod(6) internet(1) private(4) enterprise(1)
		spelio(9363) software(1) asn1c(5) test(1) 67 }
	DEFINITIONS AUTOMATIC TAGS ::=
BEGIN

	A ::= CHOICE {
		a	NULL,
		b	NULL,
		...
	}

	B ::= CHOICE {
		a	NULL,
		b	NULL,
		...,
		other	A	-- Only AUTOMATIC TAGS make it right
	}

	C ::= SET {
		a	NULL,
		b	NULL,
		...,
		other1	A,
		other2	B
	}

END
