-- OK: Everything is fine

-- iso.org.dod.internet.private.enterprise (1.3.6.1.4.1)
-- .spelio.software.asn1c.test (9363.1.5.1)
-- .82

ModuleTestWithComponents
	{ iso org(3) dod(6) internet(1) private(4) enterprise(1)
		spelio(9363) software(1) asn1c(5) test(1) 82 }
	DEFINITIONS ::=
BEGIN

	BunchOfStrings ::= SEQUENCE OF VisibleString
	Address ::= BunchOfStrings (SIZE (1..6)) (WITH COMPONENT (SIZE (1..32)))

	Type ::= SEQUENCE {
		one INTEGER DEFAULT 1
	} (WITH COMPONENTS { ..., one (1) PRESENT })

END
