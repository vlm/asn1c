-- OK: Everything is fine

-- Behavioral regression test for CVE-2025-32893. Companion to the
-- compilation/golden test 163: where 163 checks that the *generated code*
-- forks into two distinct information object tables, this spec is compiled
-- and the generated decoder is actually *run* (see
-- tests-c-compiler/check-src/check-164.-fcompound-names.c).
--
-- SetA and SetB intentionally reuse the SAME &id (1) but bind it to
-- DIFFERENT types (IntPayload vs StrPayload). `Message.second' is
-- parameterized by SetB, so its open type at id 1 must decode as an
-- IA5String. Without the fix, asn1f_parameterization_fork() fails to fork the
-- two parameterizations and `second' silently reuses SetA's table (id 1 maps
-- to an INTEGER), so the very same encoding decodes differently. The runtime
-- test detects that: a value valid under SetB is rejected, and vice versa.

-- iso.org.dod.internet.private.enterprise (1.3.6.1.4.1)
-- .spelio.software.asn1c.test (9363.1.5.1)
-- .164

ModuleIosValuesetBehavior
	{ iso org(3) dod(6) internet (1) private(4) enterprise(1)
		spelio(9363) software(1) asn1c(5) test(1) 164 }
	DEFINITIONS AUTOMATIC TAGS ::=
BEGIN

    Id ::= INTEGER

    P ::= CLASS {
        &id     Id UNIQUE,
        &Type
    } WITH SYNTAX { TYPE &Type IDENTIFIED BY &id }

    IntPayload  ::= INTEGER
    BoolPayload ::= BOOLEAN
    StrPayload  ::= IA5String
    OctPayload  ::= OCTET STRING

    SetA P ::= {
        {TYPE IntPayload  IDENTIFIED BY 1} |
        {TYPE BoolPayload IDENTIFIED BY 2}
    }

    SetB P ::= {
        {TYPE OctPayload  IDENTIFIED BY 2} |
        {TYPE StrPayload  IDENTIFIED BY 1}
    }

    Message ::= SEQUENCE {
        first   SpecializedContent {{SetA}},
        second  SpecializedContent {{SetB}}
    }

    SpecializedContent {P : Set} ::= SEQUENCE {
        id      P.&id({Set}),
        value   P.&Type({Set}{@id})
    }

END
