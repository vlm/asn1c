-- SE: Semantic error

-- iso.org.dod.internet.private.enterprise (1.3.6.1.4.1)
-- .spelio.software.asn1c.test (9363.1.5.1)
-- .4

ModuleTestEnum2
	{ iso org(3) dod(6) internet (1) private(4) enterprise(1)
		spelio(9363) software(1) asn1c(5) test(1) 4 }
	DEFINITIONS ::=
BEGIN

	enum1 Enum1 ::= blue

	Enum1 ::= ENUMERATED { red, green, ...,
		blue(1) -- collides with green -- }

END
