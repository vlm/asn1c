Test DEFINITIONS AUTOMATIC TAGS ::=
BEGIN
    StationID ::= INTEGER(0..4294967295)

    TimestampIts ::= INTEGER {utcStartOf2004(0), oneMillisecAfterUTCStartOf2004(1)} (0..4398046511103)

    AccelerationControl ::= BIT STRING {
        brakePedalEngaged (0),
        gasPedalEngaged (1),
        emergencyBrakeEngaged (2),
        collisionWarningEngaged (3),
        accEngaged (4),
        cruiseControlEngaged (5),
        speedLimiterEngaged (6)
    } (SIZE(7))

    MyCar ::= SEQUENCE {
        id StationID,
        acceleration AccelerationControl OPTIONAL,
        detectionTime TimestampIts
    }

END
