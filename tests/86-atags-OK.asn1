-- OK: Everything is fine

-- iso.org.dod.internet.private.enterprise (1.3.6.1.4.1)
-- .spelio.software.asn1c.test (9363.1.5.1)
-- .86

ModuleAutoTags
	{ iso org(3) dod(6) internet (1) private(4) enterprise(1)
		spelio(9363) software(1) asn1c(5) test(1) 86 }
	DEFINITIONS AUTOMATIC TAGS ::=
BEGIN

	A ::= SEQUENCE { a INTEGER }
	B ::= SEQUENCE { a [0] INTEGER }
	C ::= SEQUENCE { a [0] IMPLICIT INTEGER }
	D ::= SEQUENCE { a [0] EXPLICIT INTEGER }
	E ::= SEQUENCE { a [0] CHOICE { b INTEGER } }

END
