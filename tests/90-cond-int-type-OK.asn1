-- OK: Everything is fine

-- iso.org.dod.internet.private.enterprise (1.3.6.1.4.1)
-- .spelio.software.asn1c.test (9363.1.5.1)
-- .90

ModuleConditionalIntegerType
	{ iso org(3) dod(6) internet (1) private(4) enterprise(1)
		spelio(9363) software(1) asn1c(5) test(1) 90 }
DEFINITIONS ::=
BEGIN

	CN-IntegerUnlimited	::= INTEGER
	CN-IntegerMinMax	::= INTEGER (MIN..MAX)
	CN-IntegerMinLow	::= INTEGER (MIN..1)
	NO-IntegerMinHigh	::= INTEGER (MIN..3000000000)
	NO-IntegerLowHigh	::= INTEGER (1..3000000000)
	CN-IntegerLowMax	::= INTEGER (1..MAX)
	NO-IntegerHighMax	::= INTEGER (3000000000..MAX)
	NO-IntegerLowestMax	::= INTEGER (-3000000000..MAX)
	NO-IntegerOutRange	::= INTEGER (3000000000..3000000001)
	NO-IntegerOutValue	::= INTEGER (3000000000)
	OK-IntegerInRange1	::= INTEGER (-100..100)
	OK-IntegerInRange2	::= INTEGER (-100|100)
	OK-IntegerInRange3	::= INTEGER (-2147483648..2147483647)
	OK-IntegerInRange4	::= INTEGER (-2147483648|2147483647)
	OK-IntegerInRange5	::= INTEGER (-2147483648|2147483647,...)
	NO-IntegerInRange6	::= INTEGER (0..4294967295)
	CN-IntegerEnumerated1	::= INTEGER { a(1), b(2) }
	NO-IntegerEnumerated2	::= INTEGER { a(1), b(3000000000) }

END
