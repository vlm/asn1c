-- OK: Everything is fine

-- iso.org.dod.internet.private.enterprise (1.3.6.1.4.1)
-- .spelio.software.asn1c.test (9363.1.5.1)
-- .127

ModulePERLong
	{ iso org(3) dod(6) internet (1) private(4) enterprise(1)
		spelio(9363) software(1) asn1c(5) test(1) 127 }
	DEFINITIONS AUTOMATIC TAGS ::=
BEGIN

	T ::= SEQUENCE {
		small32range	INTEGER (-2000000000..2000000000),
		full32range	INTEGER (-2147483648..2147483647),
		unsigned32	INTEGER (0..4294967295),
		unsplit32	INTEGER (5..500|600..4294967290)
	}

END
