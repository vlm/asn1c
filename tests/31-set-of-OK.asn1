-- OK: Everything is fine

-- iso.org.dod.internet.private.enterprise (1.3.6.1.4.1)
-- .spelio.software.asn1c.test (9363.1.5.1)
-- .31

ModuleTestSetOfSimple
	{ iso org(3) dod(6) internet(1) private(4) enterprise(1)
		spelio(9363) software(1) asn1c(5) test(1) 31 }
	DEFINITIONS IMPLICIT TAGS ::=
BEGIN

	Forest ::= SET OF Tree

	Tree ::= SEQUENCE {
		height	INTEGER,
		width	INTEGER
	}

	-- The following clause tests OPTIONAL.
	Stuff ::= SET {
			trees    [1] SET OF Forest OPTIONAL,
			...,
			other    CHOICE {
				a [0] INTEGER,
				b [3] INTEGER
			},
			...,
			anything [2] SET OF
				SEQUENCE {
					cup-of-coffee	BIT STRING,
					...
				} OPTIONAL
			-- The above OPTIONAL applies to the "anything"
			-- member of the outer CHOICE,
			-- not to the SET OF's embedded SEQUENCE!
		}

	SSS ::= SEQUENCE OF SET OF SEQUENCE OF BIT STRING

END
