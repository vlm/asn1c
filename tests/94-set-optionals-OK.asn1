-- OK: Everything is fine

-- iso.org.dod.internet.private.enterprise (1.3.6.1.4.1)
-- .spelio.software.asn1c.test (9363.1.5.1)
-- .94

ModuleSetOptionals
	{ iso org(3) dod(6) internet (1) private(4) enterprise(1)
		spelio(9363) software(1) asn1c(5) test(1) 94 }
	DEFINITIONS AUTOMATIC TAGS ::=
BEGIN

	TestSet ::= SET {
		m0 [0] IMPLICIT VisibleString,
		m1 [1] IMPLICIT VisibleString OPTIONAL,
		m2 [2] IMPLICIT VisibleString,
		m3 [3] IMPLICIT VisibleString,
		m4 [4] IMPLICIT VisibleString OPTIONAL,
		m5 [5] IMPLICIT VisibleString,
		m6 [6] IMPLICIT VisibleString,
		m7 [7] IMPLICIT VisibleString,
		m8 [8] IMPLICIT VisibleString OPTIONAL,
		m9 [9] IMPLICIT VisibleString,
		...
	}

END
