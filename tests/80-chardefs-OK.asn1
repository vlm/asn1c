-- OK: Everything is fine

-- iso.org.dod.internet.private.enterprise (1.3.6.1.4.1)
-- .spelio.software.asn1c.test (9363.1.5.1)
-- .80

ModuleCharacterDefinitions
	{ iso org(3) dod(6) internet(1) private(4) enterprise(1)
		spelio(9363) software(1) asn1c(5) test(1) 80 }
	DEFINITIONS ::=
BEGIN
	-- Elements taken from ASN1-CHARACTER-MODULE (X.680:07/2002)
	-- { joint-iso-itu-t asn1(1) specification(0) modules(0) iso10646(0) }
	nul IA5String ::= {0, 0}
	null BMPString ::= {0, 0, 0, 0}
	space BMPString ::= {0, 0, 0, 32}
	tilde BMPString ::= {0, 0, 0, 126}

	BasicLatin ::= BMPString(FROM (space..tilde))
	BasicGreek ::= BMPString(FROM ({0, 0, 3, 112}..{0, 0, 3, 207}))

	NotSpace ::= BMPString (FROM(ALL EXCEPT space))

END
