-- OK: Everything is fine

-- iso.org.dod.internet.private.enterprise (1.3.6.1.4.1)
-- .spelio.software.asn1c.test (9363.1.5.1)
-- .110

ModuleParameterization3
	{ iso org(3) dod(6) internet (1) private(4) enterprise(1)
		spelio(9363) software(1) asn1c(5) test(1) 110 }
	DEFINITIONS ::=
BEGIN

	Flag{Color} ::= SEQUENCE {
		field	Color DEFAULT blue
	}

	IntegerColorFlag ::= Flag{INTEGER{ red(0), green(1), blue(5) }}
	EnumeratedColorFlag ::= Flag{ENUMERATED{ red(3), green, blue }}

END
