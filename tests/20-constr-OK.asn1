-- OK: Everything is fine

-- iso.org.dod.internet.private.enterprise (1.3.6.1.4.1)
-- .spelio.software.asn1c.test (9363.1.5.1)
-- .20

ModuleTestConstr
	{ iso org(3) dod(6) internet(1) private(4) enterprise(1)
		spelio(9363) software(1) asn1c(5) test(1) 20 }
	DEFINITIONS IMPLICIT TAGS EXTENSIBILITY IMPLIED ::=
BEGIN

	ConstructedType1 ::= SEQUENCE {
				a	[1] INTEGER,
				b	[2] INTEGER,
				...!ex1,
				c	IA5String,
				...,
				d	UTF8String
			}

	ConstructedType2 ::= SET {
				a	[1] INTEGER,
				b	[2] INTEGER
			}

	ex1 INTEGER ::= 1

END
