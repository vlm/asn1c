-- OK: Everything is fine

-- iso.org.dod.internet.private.enterprise (1.3.6.1.4.1)
-- .spelio.software.asn1c.test (9363.1.5.1)
-- .32

ModuleTestSequenceSimple
	{ iso org(3) dod(6) internet(1) private(4) enterprise(1)
		spelio(9363) software(1) asn1c(5) test(1) 32 }
	DEFINITIONS IMPLICIT TAGS ::=
BEGIN

	Programming ::= SEQUENCE SIZE(1..maxSize) OF [0] IMPLICIT Fault

	Fault ::= SET OF Error

	Error ::= SEQUENCE {
			...
		}

	maxSize INTEGER ::= 10

END
