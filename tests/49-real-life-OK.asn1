-- OK: Everything is fine

-- iso.org.dod.internet.private.enterprise (1.3.6.1.4.1)
-- .spelio.software.asn1c.test (9363.1.5.1)
-- .49

ModuleSetChoiceExtensibility
	{ iso org(3) dod(6) internet (1) private(4) enterprise(1)
		spelio(9363) software(1) asn1c(5) test(1) 49 }
	DEFINITIONS ::=
BEGIN
	/*
	 * 0.8.17 had problem parsing this module
	 */

	EXPORTS TypeA ;

	IMPORTS TypeB FROM ModuleB
        	TypeC FROM ModuleC ;

END
