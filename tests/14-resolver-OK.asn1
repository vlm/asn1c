-- OK: Everything is fine

-- iso.org.dod.internet.private.enterprise (1.3.6.1.4.1)
-- .spelio.software.asn1c.test (9363.1.5.1)
-- .14 1
-- .14 2

ModuleTestResolver2
	{ iso org(3) dod(6) internet(1) private(4) enterprise(1)
		spelio(9363) software(1) asn1c(5) test(1) 14 1 }
	DEFINITIONS ::=
BEGIN
	IMPORTS Enumeration, beta FROM
		OtherModuleRenamed
		{ iso org(3) dod(6) internet(1) private(4) enterprise(1)
			spelio(9363) software(1) asn1c(5) test(1) 14 2 };

	-- external reference
	alpha Enumeration ::= beta

	-- 
	-- The following are for post-fix checking by the check_fixer.
	-- It will be able to pick-up these values if the file is parseable,
	-- even if it contains some semantic errors.
	-- 

	check-alpha INTEGER ::= 2

END

ModuleTestResolver3
	{ iso org(3) dod(6) internet(1) private(4) enterprise(1)
		spelio(9363) software(1) asn1c(5) test(1) 14 2 }
	DEFINITIONS ::=
BEGIN
	EXPORTS Enumeration, beta ;

	beta HiddenEnum ::= b

	HiddenEnum ::= ENUMERATED { a(1), b(2) }

	Enumeration ::= ENUMERATED { a(1), b(2) }	-- the same type --

END
