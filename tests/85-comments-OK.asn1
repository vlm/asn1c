-- OK: Everything is fine

-- iso.org.dod.internet.private.enterprise (1.3.6.1.4.1)
-- .spelio.software.asn1c.test (9363.1.5.1)
-- .85

ModuleTestComments
	{ iso org(3) dod(6) internet (1) private(4) enterprise(1)
		spelio(9363) software(1) asn1c(5) test(1) 85 }
	DEFINITIONS ::=
BEGIN

	T1 ::= SEQUENCE--comment-- { ... }
	T2 ::= SEQUENCE-- comment-- { ... }
	T3 ::= SEQUENCE--- comment --- { ... }
	T4 ::= SEQUENCE----comment---- { ... }
	T5 ::= SEQUENCE---- comment ---- { ... }

	----- Another ambiguous comment ---

	-- Immediately terminating ambiguous comment ----
	-------------
	-- cmt1 ---- cmt2 ----

END
