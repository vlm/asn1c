-- OK: Everything is fine

-- iso.org.dod.internet.private.enterprise (1.3.6.1.4.1)
-- .spelio.software.asn1c.test (9363.1.5.1)
-- .126

ModulePERExtensions
	{ iso org(3) dod(6) internet (1) private(4) enterprise(1)
		spelio(9363) software(1) asn1c(5) test(1) 126 }
	DEFINITIONS AUTOMATIC TAGS ::=
BEGIN

	PDU ::= SEQUENCE {
		...,
		str-o	IA5String	OPTIONAL,
		str-m	IA5String,
		singl	Singleton,
		pdu-2	PDU-2	OPTIONAL
	}

	Singleton ::= SEQUENCE {
		opt-z	IA5String DEFAULT "z"
	}

	PDU-2 ::= CHOICE {
		main [3] INTEGER,
		...,
		ext1 [1] INTEGER,
		ext0 [0] INTEGER
	}

END
