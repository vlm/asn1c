-- OK: Everything is fine

-- iso.org.dod.internet.private.enterprise (1.3.6.1.4.1)
-- .spelio.software.asn1c.test (9363.1.5.1)
-- .93

Module-asn1c-controls
	{ iso org(3) dod(6) internet (1) private(4) enterprise(1)
		spelio(9363) software(1) asn1c(5) test(1) 93 }
DEFINITIONS AUTOMATIC TAGS ::=
BEGIN

	Sequence ::= SEQUENCE {
		ainl INTEGER,
		aptr INTEGER	/* <asn1c:pointer> */
	}

	Set ::= SET {
		ainl Sequence,
		aptr Sequence	-- <asn1c:pointer>
	}

	Choice ::= CHOICE {
		setof SET OF INTEGER, -- <asn1c:pointer>
		aptr Sequence,	-- <asn1c:pointer>
		ainl Sequence
	}

END
