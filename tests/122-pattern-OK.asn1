-- OK: Everything is fine

-- iso.org.dod.internet.private.enterprise (1.3.6.1.4.1)
-- .spelio.software.asn1c.test (9363.1.5.1)
-- .122

ModulePatternConstraint
	{ iso org(3) dod(6) internet (1) private(4) enterprise(1)
		spelio(9363) software(1) asn1c(5) test(1) 122 }
	DEFINITIONS AUTOMATIC TAGS ::=
BEGIN

	Language ::= VisibleString (FROM ("a".."z" | "A".."Z" | "-" | "0".."9"))
		(PATTERN "[a-zA-Z]#(1,8)(-[a-zA-Z0-9]#(1,8))*")

	PatternByRef1 ::= VisibleString (PATTERN refPattern1)
	PatternByRef2 ::= VisibleString (PATTERN refPattern2)

	refPattern1 UniversalString ::= "[a-zA-Z]#(1,8)(-[a-zA-Z0-9]#(1,8))*"
	refPattern2 UTF8String ::= "[a-zA-Z]#(1,8)(-[a-zA-Z0-9]#(1,8))*"

END
