-- OK: Everything is fine

-- iso.org.dod.internet.private.enterprise (1.3.6.1.4.1)
-- .spelio.software.asn1c.test (9363.1.5.1)
-- .60

ModuleTestANY
	{ iso org(3) dod(6) internet(1) private(4) enterprise(1)
		spelio(9363) software(1) asn1c(5) test(1) 60 }
	DEFINITIONS IMPLICIT TAGS ::=
BEGIN

	T1 ::= SEQUENCE {
		i	INTEGER,
		any	ANY
	}

	T2 ::= SEQUENCE {
		i	INTEGER,
		any	[0] ANY OPTIONAL
	}

	T3 ::= SEQUENCE {
		any1	ANY,
		any2	ANY
	}

END
